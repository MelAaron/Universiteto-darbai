(defun c:ManoFigura2()

  (command "color" 24)
  (setq Pradzia (getpoint "Pradinis Taskas"))
  (setq K2 (list (car Pradzia) (+(cadr Pradzia)50)))
  (setq K3 (list (+(car Pradzia)60) (cadr Pradzia)))
  (setq K4 (list (car K3) (+(cadr K3)50)))
  (command "line" K2 Pradzia K3 K4 "")

  (command "color" 104)
  (setq EG1 (list (-(car K2)100) (cadr K2)))
  (setq EG2 (list (+(car K4)100) (cadr K4)))
  (setq EG3 (list (+(car EG1)40) (+(cadr EG1)40)))
  (setq EG4 (list (-(car EG2)40) (+(cadr EG2)40)))
  (setq EG5 (list (-(car EG3)20) (cadr EG3)))
  (setq EG6 (list (+(car EG4)20) (cadr EG4)))
  (setq EG7 (list (+(car EG5)40) (+(cadr EG5)40)))
  (setq EG8 (list (-(car EG6)40) (+(cadr EG6)40)))
  (setq EG9 (list (-(car EG7)20) (cadr EG8)))
  (setq EG10 (list (+(car EG8)20) (cadr EG8)))
  (setq EG11 (list (+(car EG9)40) (+(cadr EG9)40)))
  (setq EG12 (list (-(car EG10)40) (+(cadr EG10)40)))
  (setq EG13 (list (-(car EG11)20) (cadr EG11)))
  (setq EG14 (list (+(car EG12)20) (cadr EG12)))
  (setq EG15 (list (+(car EG13)40) (+(cadr EG13)40)))
  (setq EG16 (list (-(car EG14)40) (+(cadr EG14)40)))
  (setq EG17 (list (-(car EG15)20) (cadr EG15)))
  (setq EG18 (list (+(car EG16)20) (cadr EG16)))
  (setq EG19 (list (+(car EG17)40) (+(cadr EG17)40)))
  (setq EG20 (list (-(car EG18)40) (+(cadr EG18)40)))
  (setq EG21 (list (+(car EG19)10) (+(cadr EG19)10)))
  (command "line" EG21 EG20 EG18 EG16 EG14 EG12 EG10 EG8 EG6 EG4 EG2 EG1 EG3 EG5 EG7 EG9 EG11 EG13 EG15 EG17 EG19 EG21 "")

  (command "color" 1)
  (setq O1 (list (+(car EG1)70) (+(cadr EG1)20)))
  (command "circle" O1 10)
  (command "-hatch" "properties" "solid" O1 "")

  (command "color" 2)
  (setq O2 (list (+(car EG1)140) (+(cadr EG1)40)))
  (command "circle" O2 10)
  (command "-hatch" "properties" "solid" O2 "")

  (command "color" 4)
  (setq O3 (list (+(car EG1)100) (+(cadr EG1)100)))
  (command "circle" O3 10)
  (command "-hatch" "properties" "solid" O3 "")

  (command "color" 5)
  (setq O4 (list (+(car EG1)140) (+(cadr EG1)150)))
  (command "circle" O4 10)
  (command "-hatch" "properties" "solid" O4 "")

  (command "color" 6)
  (setq O5 (list (+(car EG1)180) (+(cadr EG1)80)))
  (command "circle" O5 10)
  (command "-hatch" "properties" "solid" O5 "")

  (setq Spalva (list (+(car EG1)130) (+(cadr EG1)50)))
  (command "color" 104)
  (command "-hatch" "properties" "solid" Spalva "")

  (setq Spalva1 (list (+(car Pradzia)30) (+(cadr Pradzia)25)))
  (command "color" 24)
  (command "-hatch" "properties" "solid" Spalva1 "")
  )
